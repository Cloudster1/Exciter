# Brake controller
Brake controller, supplier view

# Specification: Brake controller SRS

## _o_h1: Braking (Heading)

### SR-1: Stop within 40 m (Software Requirement)
The vehicle shall stop within 40 m from 80 km/h.
| Surface | Distance |
| --- | --- |
| Dry | 40 m |
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- Risk: High
- Platforms: Truck, Bus
- Weight: 12.5
- Test cases: 3
- Safety relevant: true
- Due: 2026-12-01T00:00:00+01:00

### _o_r2: Warn the driver (Software Requirement)
A warning sounds when the brake pressure P_b drops, when the brakes fade.
- Risk: Low
- satisfies -> SR-1

## _not_content
