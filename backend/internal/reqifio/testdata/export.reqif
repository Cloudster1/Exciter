# Brakes
Exported from the project BRK.

# Specification: Brakes

## BRK-R1: Braking (Section)

### BRK-R2: Stop within 40 m (Interface)
The vehicle shall stop within 40 m.
- on dry roads
| Surface | Dry |  |
| --- | --- | --- |
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- Rationale: Law.
- Status: Draft
- Priority: Must
- Owner: ada@example.com
- Labels: brakes, safety
- Risk: High
- Tags: Truck, Bus
- Notes: Dry road
- Detail: Measured.
- Weight: 12.5
- Due: 2026-12-01T00:00:00.000Z
- Safe: true
- Reference: https://example.com/brakes
- Reviewer: ada@example.com

## BRK-R3: Warn the driver (Requirement)
A tone sounds.
- Derives -> BRK-R2

# Specification: Glossary

## R4: Brake pedal (Glossary term)
- Definition: The pedal that slows the car.
- Synonyms: pedal, brake
- Avoid: stopper
- Status: approved
